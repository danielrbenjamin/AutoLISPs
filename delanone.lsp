(defun c:delanonE ( / ss i ename bname )
  (vl-load-com)
  (setq ss (ssget "_X" '((0 . "INSERT"))))
  (if ss
    (progn
      (setq i 0)
      (while (< i (sslength ss))
        (setq ename (ssname ss i)
              bname (cdr (assoc 2 (entget ename)))
        )
        (if (wcmatch bname "*E*")
          (entdel ename)
        )
        (setq i (1+ i))
      )
      (princ "\nDeleted all block references with names starting with *E.")
    )
    (princ "\nNo block references found.")
  )
  (princ)
)
